standard library package AiProvenanceLibrary {
    doc /*
     * SysON project addition to the SysML v2 standard library.
     *
     * Marks model elements that were generated by the AI modeling assistant and accepted
     * by a reviewer, so that generated content is distinguishable from hand-authored
     * content for as long as it lives in the model. plan.md item 4 lists this as a
     * non-negotiable: a derived requirement that silently entered a baseline is a problem
     * you want to catch in the tool, not in a design review.
     *
     * This file is the canonical, human-authored source of truth. It is not loaded
     * directly at runtime: it is compiled into ../sysml.libraries/AiProvenance.json
     * by AiProvenanceLibraryGenerator (see src/test/java), which is re-run by hand
     * whenever this file changes.
     */

    private import ScalarValues::String;

    metadata def Generated {
        doc /*
         * Applied to an element created from an accepted AI proposal.
         *
         * The prompt that produced the element is deliberately NOT stored here. Free text
         * would have to be embedded as a SysML string literal, and this project has already
         * been bitten by the fact that a quotation mark inside such a literal cannot be
         * escaped (see plan.md item 3). proposalId points at the row in ai_proposal that
         * holds the prompt, the model, the author and every other candidate from the same
         * run, which is both safer and more complete than a truncated copy here.
         *
         * The names are generatedBy/generatedAt rather than the shorter by/at that plan.md
         * originally sketched: `by`, `at` and `when` are reserved, and an attribute using one
         * is dropped silently - along with every attribute declared after it in the same body
         * - with zero parse reports. Measured, see plan.md item 4.
         */

        attribute generatedBy : String;

        attribute generatedAt : String;

        attribute proposalId : String;
    }
}
